# requirements

## requirements: References to requirements.docx (Container)
Read-only references to Microsoft Word document.
- srcFileChecksum: DBC23EB0BE6E9DB677F07371BDC078EE

### 1 ХАРАКТЕРИСТИКИ ПЛАВАТЕЛЬНОГО СРЕДСТВА (Functional)
1 ХАРАКТЕРИСТИКИ ПЛАВАТЕЛЬНОГО СРЕДСТВА
Подводная лодка оснащена командной рубкой. Низкая масса за счёт продуманной схемы энергетической установки позволила использовать прочный корпус толщиной 21,5 миллиметров. Рабочая глубина погружения подводной лодки составляет 120 метров, а предельная глубина – 180 метров. Расчётной глубиной разрушения корпуса является 300 метров. Общая низкая масса приводит к повышенной маневренности и скорости. Кроме того, подводная лодка оснащена дополнительным инклинометром в центральном отсеке.
Водоизмещение: 769 тонн.
Мощность 3200 лошадиные силы.
Скорость: 17,7 узлов | 32 километра в час.
Глубина погружения: 250 метров.
Дальность хода: 8500 морских миль | 15740 километров.
Длина: 67,10 метров.
Ширина: 6,20 метров.
Осадка: 4,74 метра.
Высота: 9,60 метров.
Экипаж: 27.
Все зависимости в данной ревизии считаются линейными. На рисунке 1.1 указана структурно-функциональная модель (без управляющих связей).
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Рисунок 1.1 – Структурно функциональная модель

### 2 ВНЕШНЯЯ ПАЛУБА (OD) (Functional)
2 ВНЕШНЯЯ ПАЛУБА (OD)
Не моделируется в данной ревизии.

### 3 КОМАНДНАЯ РУБКА (CR) (Functional)
3 КОМАНДНАЯ РУБКА (CR)
Не моделируется в данной ревизии.

### 4 ГЛАВНАЯ БАЛЛАСТНАЯ ЦИСТЕРНА (MBS) (Functional)
4 ГЛАВНАЯ БАЛЛАСТНАЯ ЦИСТЕРНА (MBS)
Существует 5 независимых друг от друга балластных цистерн.
Каждая балластная цистерна может изменить уровень затопления с 0 до 100% примерно за 12,5 секунд при 1 атмосфере.
Главная балластная цистерна может изменить уровень затопления с 100% до 0% примерно за 30 секунд, потратив 70 атмосфер сжатого воздуха при 1 атмосфере.
При 0% заполнении балластных цистерн подводная лодка имеет положительную плавучесть (1,66 метров в секунду к поверхности).
При 100% заполнении балластных цистерн подводная лодка имеет нейтральную плавучесть.
В данной ревизии хранит запас сжатого воздуха.
На рисунке 4.1 указана схема подключения MBS, в таблице 4.1 – характеристики интерфейсов
Таблица 4.1 – Характеристика интерфейсов MBS
| Имя интерфейса | Тип интерфейса | Функции системы 1 | Функции системы 2 | Компонент системы 1 | Компоненты системы 2 | Примечания |
| --- | --- | --- | --- | --- | --- | --- |
| floodingLevel | Analog | MBS предаёт данные ES | ES принимает данные MBS | MBS | ES | f(fv1, fv2, fv3, fv4, fv5, pv, d, c) |
| fillingValve1 | Analog | BTS передаёт данные MBS | MBS принимает данные BTS | BTS | MBS | fv1 |
| fillingValve2 | Analog | BTS передаёт данные MBS | MBS принимает данные BTS | BTS | MBS | fv2 |
| fillingValve3 | Analog | BTS передаёт данные MBS | MBS принимает данные BTS | BTS | MBS | fv3 |
| fillingValve4 | Analog | BTS передаёт данные MBS | MBS принимает данные BTS | BTS | MBS | fv4 |
| fillingValve5 | Analog | BTS передаёт данные MBS | MBS принимает данные BTS | BTS | MBS | fv5 |
| purgingValves | Analog | BTS передаёт данные MBS | MBS принимает данные BTS | BTS | MBS | pv |
| depth | Analog | ES передаёт данные MBS | MBS принимает данные ES | ES | MBS | d |
| ecActivate | Discrete | EC передаёт данные MBS | EC принимает данные BTS | EC | MBS | eca |
| dcActivate | Discrete | DC передаёт данные MBS | MBS принимает данные DC | DC | MBS | dca |
| compressedAir | Analog | Внутренний сигнал |  | MBS |  | f(pv, ec, dca)=c |
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Рисунок 4.1 – Схема подключения MBS

### 5 КОРМОВОЙ ОТСЕК (AFTC) (Functional)

#### 5.1 Электронный компрессор (EC) (Functional)
5.1 Электронный компрессор (EC)
Пополняет запасы сжатого воздуха.
Может изменить запас сжатого воздуха с 0% (0 атмосфер) до 100% (240 атмосфер) за 20 минут.
Потребляет 12 условных единиц заряда батарей в минуту.
Потребляет 62 условных единиц качества воздуха в минуту.
На рисунке 5.1 указана схема подключения EC, в таблице 5.1 – характеристики интерфейсов
Таблица 5.1 – Характеристика интерфейсов EC
| Имя интерфейса | Тип интерфейса | Функции системы 1 | Функции системы 2 | Компонент системы 1 | Компоненты системы 2 | Примечания |
| --- | --- | --- | --- | --- | --- | --- |
| ecActivate | Discrete | EC передаёт данные MBS | MBC принимает данные EC | EC | MBS | f(bc, ece) |
| ecActivate | Discrete | EC передаёт данные EM | EM принимает данные EC | EC | EM | f(bc, ece) |
| ecActivate | Discrete | EC передаёт данные V | V принимает данные EC | EC | V | f(bc, ece) |
| batteryCharge | Analog | EM передаёт данные EC | EC принимает данные EM | EM | EC | bc |
| ecEnable | Discrete | CP передаёт данные EP | EC принимает данные CP | CP | EC | ece |
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Рисунок 5.1 – Схема подключения EC

#### 5.2 Дизель-компрессор (DC) (Functional)
5.2 Дизель-компрессор (DC)
Пополняет запасы сжатого воздуха.
Может изменить запас сжатого воздуха с 0% (0 атмосфер) до 100% (240 атмосфер) за 6 минут.
Потребляет 9 литров топлива в минуту.
Потребляет 200 условных единиц качества воздуха в минуту.
На рисунке 5.2 указана схема подключения DC, в таблице 5.2 – характеристики интерфейсов
Таблица 5.2 – Характеристика интерфейсов DC
| Имя интерфейса | Тип интерфейса | Функции системы 1 | Функции системы 2 | Компонент системы 1 | Компоненты системы 2 | Примечания |
| --- | --- | --- | --- | --- | --- | --- |
| dcActivate | Discrete | DC передаёт данные MBS | MBC принимает данные EC | DC | MBS | f(f, dce) |
| dcActivate | Discrete | DC передаёт данные DE | DE принимает данные EC | DC | DE | f(f, dce) |
| dcActivate | Discrete | C передаёт данные V | V принимает данные EC | DC | V | f(f, dce) |
| fuel | Analog | DE передаёт данные DC | DC принимает данные DE | DE | DC | f |
| dcEnable | Discrete | CP передаёт данные DC | DC принимает данные CP | CP | DC | dce |
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Рисунок 5.2 – Схема подключения DC

#### 5.3 Электромоторы (EM) (Functional)
5.3 Электромоторы (EM)
В таблице 5.3 указаны характеристики работы электромоторов при разных режимах работы. Ускорение равно 1 километр в час в секунду.
Таблица 5.3 – Характеристики работы электромоторов
| Режим работы | Скорость (километр в час) | Потребление заряда батарей (условная единица в минуту) |
| --- | --- | --- |
| Самый полный вперёд | 19 | 7 |
| Полный вперёд | 16 | 6 |
| Средний вперёд | 13 | 5 |
| Малый вперёд | 10 | 3 |
| Самый малый вперёд | 6 | 1 |
| Обе машины стоп | 0 | 0 |
| Зарядка батарей | 0 | 0 |
| Самый малый назад | -9 | 3 |
| Малый назад | -12 | 4 |
| Средний назад | -14 | 5 |
| Самый полный назад | -16 | 6 |
На рисунке 5.3 указана схема подключения DC, в таблице 5.4 – характеристики интерфейсов
Таблица 5.4 – Характеристика интерфейсов DC
| Имя интерфейса | Тип интерфейса | Функции системы 1 | Функции системы 2 | Компонент системы 1 | Компоненты системы 2 | Примечания |
| --- | --- | --- | --- | --- | --- | --- |
| emWorkMode | Analog | EM передаёт данные G | G принимает данные EM | EM | G | f(ece, dewm, pa, emom, eme) |
| batteryCharge | Analog | EM передаёт данные EC | EC принимает данные EM | EM | EC | f(ece, dewm, pa, emom, eme) |
| batteryCharge | Analog | EM передаёт данные DE | E принимает данные EM | EM | DE | f(ece, dewm, pa, emom, eme) |
| batteryCharge | Analog | EM передаёт данные P | P принимает данные EM | EM | P | f(ece, dewm, pa, emom, eme) |
| ecActivate | Discrete | EC передаёт данные EM | EM принимает данные EC | EC | EM | eca |
| deWorkMode | Analog | DE передаёт данные EM | EM принимает данные DE | DE | EM | dewm |
| pActivate | Analog | P передаёт данные EM | EM принимает данные P | P | EM | pa |
| operatingMode | Analog | MT передаёт данные EM | EM принимает данные MT | MT | EM | emom |
| emEnable | Discrete | MT передаёт данные EM | EM принимает данные MT | MT | EM | eme |
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Рисунок 5.3 – Схема подключения DC

##### 5.3.1 Заряд батарей (BC) (Functional)
5.3.1 Заряд батарей (BC)
100% заряда батарей составляют 3000 условных единиц.

### 6 ДИЗЕЛЬНЫЙ ОТСЕК (DIEC) (Functional)

#### 6.1 Дизеля (DE) (Functional)
6.1 Дизеля (DE)
В таблице 6.1 указаны характеристики работы дизеля в разных режимах работы. Дизеля не могут работать на любой глубине. Ускорение равно 2 километра в час в секунду.
Таблица 6.1 – Характеристики работы дизеля
| Режим работы | Скорость (километр в час) | Потребление топлива (литр в минуту) | Восполнение заряда батарей (условная единица в минуту) |
| --- | --- | --- | --- |
| Самый полный вперёд | 32 | 7,7 \| 7,7 | 0 |
| Полный вперёд | 28 | 8,6 \| 7,6 | 20,2 |
| Средний вперёд | 24 | 7,6 \| 4,4 | 64,7 |
| Малый вперёд | 18 | 6 \| 3,3 | 62,7 |
| Самый малый вперёд | 6 | 8,2 \| 2,6 | 128,9 |
| Обе машины стоп | 0 | 0 \| 0 | 0 |
| Зарядка батарей | 0 | 2 \| 0 | 50 |
| Самый малый назад | -10 | 4,6 \| 2 | 65,2 |
| Малый назад | -14 | 4,2 \| 2 | 49,9 |
| Средний назад | -18 | 4,3 \| 2,8 | 34 |
| Самый полный назад | -20 | 4,6 \| 4,6 | 0 |

##### 6.1.1 Топливо (F) (Functional)
6.1.1 Топливо (F)
100% топлива составляют 50000 литров.
На рисунке 6.1 указана схема подключения DE, в таблице 6.2 – характеристики интерфейсов
Таблица 6.2 – Характеристика интерфейсов DE
| Имя интерфейса | Тип интерфейса | Функции системы 1 | Функции системы 2 | Компонент системы 1 | Компоненты системы 2 | Примечания |
| --- | --- | --- | --- | --- | --- | --- |
| fuel | Analog | DE передаёт данные DC | DC принимает данные DE | DE | DC | f(dca, bc, sa, d, deom, dee) |
| deWorkMode | Analog | DE передаёт данные EM | EM принимает данные DE | DE | EM | f(dca, bc, sa, d, deom, dee) |
| deWorkMode | Analog | DE передаёт данные G | G принимает данные DE | DE | G | f(dca, bc, sa, d, deom, dee) |
| dcActivate | Discrete | DC передаёт данные DE | DE принимает данные DC | DC | DE | dca |
| batteryCharge | Analog | EM передаёт данные DE | DE принимает данные EM | EM | DE | bc |
| sActivate | Discrete | S передаёт данные DE | DE принимает данные S | S | DE | sa |
| depth | Analog | ES передаёт данные DE | DE принимает данные ES | ES | DE | d |
| operatingMode | Analog | MT передаёт данные DE | DE принимает данные MT | MT | DE | deom |
| deEnable | Discrete | MT передаёт данные DE | DE принимает данные MT | MT | DE | dee |
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Рисунок 6.1 – Схема подключения DE

#### 6.2 Шноркель (S) (Functional)
6.2 Шноркель (S)
Система труб, которая может быть выдвинута над поверхностью воды для забора свежего воздуха и обеспечения работы дизелей в подводном положении. Работает только до перископной глубины (до 8 метров).
Восполняет 400 условных единиц качества воздуха в минуту.
На рисунке 6.2 указана схема подключения S, в таблице 6.3 – характеристики интерфейсов
Таблица 6.3 – Характеристика интерфейсов S
| Имя интерфейса | Тип интерфейса | Функции системы 1 | Функции системы 2 | Компонент системы 1 | Компоненты системы 2 | Примечания |
| --- | --- | --- | --- | --- | --- | --- |
| sActivate | Discrete | S передаёт данные DE | DE принимает данные DE | S | DE | f(d,se) |
| sActivate | Discrete | S передаёт данные V | V принимает данные DE | S | V | f(d,se) |
| depth | Analog | ES передаёт данные S | S принимает данные ES | ES | S | d |
| sEnable | Discrete | CP передаёт данные S | S принимает данные CP | CP | S | se |
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Рисунок 6.2 – Схема подключения S

#### 6.3 Вентиляция (V) (Functional)
6.3 Вентиляция (V)
Вентиляция повышает качество воздуха для дыхания в течение ограниченного времени.
Во время работы вентиляция восполняет 5 условных единиц качества воздуха в минуту.

##### 6.3.1 Качество воздуха (AQ) (Functional)
6.3.1 Качество воздуха (AQ)
100% качества воздуха – 3000 условных единиц.
Экипаж потребляет 6 условных единиц качества воздуха в минуту.
Когда подводная лодка находиться на поверхности свежий воздух восполняет 6000 условных единиц качества воздуха в минуту.
На рисунке 6.3 указана схема подключения V, в таблице 6.4 – характеристики интерфейсов
Таблица 6.4 – Характеристика интерфейсов V
| Имя интерфейса | Тип интерфейса | Функции системы 1 | Функции системы 2 | Компонент системы 1 | Компоненты системы 2 | Примечания |
| --- | --- | --- | --- | --- | --- | --- |
| ecActivate | Discrete | EC передаёт данные V | V принимает данные EC | EC | V |  |
| dcActivate | Discrete | DC передаёт данные V | V принимает данные DC | DC | V |  |
| sActivate | Discrete | EM передаёт данные V | V принимает данные S | S | V |  |
| depth | Analog | ES передаёт данные V | V принимает данные ES | ES | V |  |
| vEnable | Discrete | CP передаёт данные V | V принимает данные CP | CP | V |  |
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Рисунок 6.3 – Схема подключения S

### 7 КАМБУЗ (GAL) (Functional)
7 КАМБУЗ (GAL)
Не моделируется в данной ревизии.

### 8 КОРМОВОЙ ЖИЛОЙ ОТСЕК (AFTLC) (Functional)
8 КОРМОВОЙ ЖИЛОЙ ОТСЕК (AFTLC)
Не моделируется в данной ревизии.

### 9 ЦЕНТРАЛЬНЫЙ ОТСЕК (CC) (Functional)

#### 9.1 Помпа (P) (Functional)
9.1 Помпа (P)
Помпа откачивает воду из всех отсеков. Наибольшая эффективность достигается при откачке воды из центрального отсека.
Может уменьшать уровень воды в отсеках на 4 метра кубических в минуту за 12 условных единиц заряда батареи в минуту.
На рисунке 9.1 указана схема подключения P, в таблице 9.1 – характеристики интерфейсов
Таблица 9.1 – Характеристика интерфейсов P
| Имя интерфейса | Тип интерфейса | Функции системы 1 | Функции системы 2 | Компонент системы 1 | Компоненты системы 2 | Примечания |
| --- | --- | --- | --- | --- | --- | --- |
| pActivate | Discrete | P передаёт данные EM | EM принимает данные P | P | EM | f(bc, pe) |
| batteryCharge | Analog | EM передаёт данные P | P принимает данные EM | EM | P | bc |
| pEnable | Discrete | CP передаёт данные P | P принимает данные CP | CP | P | pe |
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Рисунок 9.1 – Схема подключения P

#### 9.2 Эхолот (ES) (Functional)
9.2 Эхолот (ES)
Эхолот измеряет текущую глубину. Ультразвуковой сигнал эффективен до 150 метров. Звуковой сигнал эффективен на любой глубине.
9.2.1 Глубиномер (DG)
Эхолот в данной ревизии выполняет функции глубиномера.
На рисунке 9.2 указана схема подключения ES, в таблице 9.2 – характеристики интерфейсов
Таблица 9.2 – Характеристика интерфейсов ES
| Имя интерфейса | Тип интерфейса | Функции системы 1 | Функции системы 2 | Компонент системы 1 | Компоненты системы 2 | Примечания |
| --- | --- | --- | --- | --- | --- | --- |
| depth | Analog | ES передаёт данные DE | DE принимает данные ES | ES | DE | f(sp, fs, rs, fl) |
| depth | Analog | ES передаёт данные V | V принимает данные ES | ES | V | f(sp, fs, rs, fl) |
| depth | Analog | ES передаёт данные MBS | MBS принимает данные ES | ES | MBS | f(sp, fs, rs, fl) |
| depth | Analog | ES передаёт данные S | S принимает данные ES | ES | S | f(sp, fs, rs, fl) |
| speed | Analog | G передаёт данные ES | ES принимает данные G | G | ES | sp |
| frontSlant | Analog | DR передаёт данные ES | ES принимает данные DR | DR | ES | fs |
| rearSlant | Analog | DR передаёт данные ES | ES принимает данные DR | DR | ES | rs |
| floodingLevel | Analog | MBS передаёт данные ES | ES принимает данные MBS | MBS | ES | fl |
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Рисунок 9.2 – Схема подключения ES

#### 9.3 Гирокомпас (G) (Functional)
9.3 Гирокомпас (G)
Работающий гирокомпас повышает точность навигации. Гирокомпас – это навигационный прибор, который использует угловой момент для определения направления относительно Севера. Он в четыре раза точнее магнитного компаса и не зависит от магнитных полей, оставаясь устойчивым при различных манёврах и условиях.
Гирокомпас потребляет 1 условную единицу заряда батареи в минуту.

##### 9.3.1 Координаты (CS) (Functional)
9.3.1 Координаты (CS)
В данной ревизии хранит координаты подлодки в десятичном формате.
На рисунке 9.3 указана схема подключения G, в таблице 9.3 – характеристики интерфейсов
Таблица 9.3 – Характеристика интерфейсов G
| Имя интерфейса | Тип интерфейса | Функции системы 1 | Функции системы 2 | Компонент системы 1 | Компоненты системы 2 | Примечания |
| --- | --- | --- | --- | --- | --- | --- |
| speed | Analog | G передаёт данные DE | DE принимает данные G | G | ES | f(dewm, emwm) |
| deWorkMode | Analog | DE передаёт данные G | G принимает данные DE | DE | G | dewm |
| emWorkMode | Analog | EM передаёт данные G | G принимает данные EM | EM | G | emwm |
| axio | Analog | A передаёт данные G | G принимает данные A | A | G |  |
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Рисунок 9.3 – Схема подключения G

#### 9.4 Вентили балластных цистерн (BTS) (Functional)
9.4 Вентили балластных цистерн (BTS)
Вентили балластных цистерн на заполнение принимают значения с 0% до 100% примерно за 5 секунд.
Вентили балластных цистерн на заполнение принимают значения со 100% до 0% примерно за 5 секунд.
Вентили балластных цистерн на продув принимают значения с 0% до 100% примерно за 5 секунд.
Вентили балластных цистерн на продув принимают значения со 100% до 0% примерно за 5 секунд.
На рисунке 9.4 указана схема подключения BTS, в таблице 9.4 – характеристики интерфейсов
Таблица 9.4 – Характеристика интерфейсов BTS
| Имя интерфейса | Тип интерфейса | Функции системы 1 | Функции системы 2 | Компонент системы 1 | Компоненты системы 2 | Примечания |
| --- | --- | --- | --- | --- | --- | --- |
| fillingValve1 | Analog | MBS передаёт данные BTS | BTS принимает данные MBS | MBS | BTS |  |
| fillingValve2 | Analog | MBS передаёт данные BTS | BTS принимает данные MBS | MBS | BTS |  |
| fillingValve3 | Analog | MBS передаёт данные BTS | BTS принимает данные MBS | MBS | BTS |  |
| fillingValve4 | Analog | MBS передаёт данные BTS | BTS принимает данные MBS | MBS | BTS |  |
| fillingValve5 | Analog | MBS передаёт данные BTS | BTS принимает данные MBS | MBS | BTS |  |
| purgingValves | Analog | MBS передаёт данные BTS | BTS принимает данные MBS | MBS | BTS |  |
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Рисунок 9.4 – Схема подключения BTS

#### 9.5 Рули глубины (DR) (Functional)
9.5 Рули глубины (DR)
Передние рули принимают значения от -35 до 35 градусов вертикального отклонения.
Задние рули принимают значения от -40 до 40 градусов вертикального отклонения.
Скорость изменения положения руля равно 1 градус в секунду.
На рисунке 9.5 указана схема подключения DR, в таблице 9.5 – характеристики интерфейсов
Таблица 9.5 – Характеристика интерфейсов BTS
| Имя интерфейса | Тип интерфейса | Функции системы 1 | Функции системы 2 | Компонент системы 1 | Компоненты системы 2 | Примечания |
| --- | --- | --- | --- | --- | --- | --- |
| frontSlant | Analog | DR передаёт данные ES | ES принимает данные DR | DR | ES |  |
| rearSlant | Analog | DR передаёт данные ES | ES принимает данные DR | DR | ES |  |
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Рисунок 9.5 – Схема подключения BTS

#### 9.6 Машинный телеграф (MT) (Functional)
9.6 Машинный телеграф (MT)
Машинный телеграф имеет 11 положений.
1) Самый полный вперёд
2) Полный вперёд
3) Средний вперёд
4) Малый вперёд
5) Самый малый вперёд
6) Обе машины стоп
7) Зарядка батарей
8) Самый малый назад
9) Малый назад
10) Средний назад
11) Самый полный назад
И переключатель маршевой установки.
На рисунке 9.6 указана схема подключения MT, в таблице 9.6 – характеристики интерфейсов
Таблица 9.6 – Характеристика интерфейсов MT
| Имя интерфейса | Тип интерфейса | Функции системы 1 | Функции системы 2 | Компонент системы 1 | Компоненты системы 2 | Примечания |
| --- | --- | --- | --- | --- | --- | --- |
| operatingMode | Analog | MT передаёт данные DE | DE принимает данные MT | MT | DE |  |
| operatingMode | Analog | MT передаёт данные DE | DE принимает данные MT | MT | EM |  |
| deEnable | Discrete | MT передаёт данные DE | DE принимает данные MT | MT | DE |  |
| emEnable | Discrete | MT передаёт данные DE | DE принимает данные MT | MT | EM |  |
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Рисунок 9.6 – Схема подключения MT

#### 9.7 Аксиометр (A) (Functional)
9.7 Аксиометр (A)
Аксиометр принимает значения от -35 до 35 горизонтального отклонения.
Скорость изменения положения руля равно 1 градус в секунду.
На рисунке 9.7 указана схема подключения A, в таблице 9.7 – характеристики интерфейсов
Таблица 9.7 – Характеристика интерфейсов A
| Имя интерфейса | Тип интерфейса | Функции системы 1 | Функции системы 2 | Компонент системы 1 | Компоненты системы 2 | Примечания |
| --- | --- | --- | --- | --- | --- | --- |
| axio | Analog | A передаёт данные G | G принимает данные A | A | G |  |
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Рисунок 9.6 – Схема подключения A

### 10 НОСОВОЙ ЖИЛОЙ ОТСЕК (FLC) (Functional)
10 НОСОВОЙ ЖИЛОЙ ОТСЕК (FLC)
Не моделируется в данной ревизии.

### 11 НОСОВОЙ ОТСЕК (BOWC) (Functional)
11 НОСОВОЙ ОТСЕК (BOWC)
Не моделируется в данной ревизии.
