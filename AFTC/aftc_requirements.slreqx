# aftc_requirements

## aftc_requirements: References to aftc_requirements.docx (Container)
Read-only references to Microsoft Word document.
- srcFileChecksum: 8824202183024D0A778F5AC64FB1E3A3

### <?>: Пополняет запасы сжатого воздуха. (Functional)
Пополняет запасы сжатого воздуха.
Может изменить запас сжатого воздуха с 0% (0 атмосфер) до 100% (240 атмосфер) за 20 минут. Потребляет 12 условных единиц заряда батарей в минуту.
Потребляет 62 условных единиц качества воздуха в минуту.
На рисунке 5.1 указана схема подключения EC, в таблице 5.1 – характеристики интерфейсов
Таблица 1 – Характеристика интерфейсов EC
| Имя интерфейса | Тип интерфейса | Функции системы 1 | Функции системы 2 | Компонент системы 1 | Компоненты системы 2 | Примечания |
| --- | --- | --- | --- | --- | --- | --- |
| ecActivate | Discrete | EC передаёт данные MBS | MBC принимает данные EC | EC | MBS | f(bc, ece) |
| ecActivate | Discrete | EC передаёт данные EM | EM принимает данные EC | EC | EM | f(bc, ece) |
| ecActivate | Discrete | EC передаёт данные V | V принимает данные EC | EC | V | f(bc, ece) |
| batteryCharge | Analog | EM передаёт данные EC | EC принимает данные EM | EM | EC | bc |
| ecEnable | Discrete | CP передаёт данные EP | EC принимает данные CP | CP | EC | ece |
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Рисунок 1 – Схема подключения EC

### 2 Дизель-компрессор (DC): Дизель-компрессор (DC) (Functional)
2 Дизель-компрессор (DC)
Пополняет запасы сжатого воздуха.
Может изменить запас сжатого воздуха с 0% (0 атмосфер) до 100% (240 атмосфер) за 6 минут. Потребляет 9 литров топлива в минуту.
Потребляет 200 условных единиц качества воздуха в минуту.
На рисунке 5.2 указана схема подключения DC, в таблице 2 – характеристики интерфейсов
Таблица 2 – Характеристика интерфейсов DC
| Имя интерфейса | Тип интерфейса | Функции системы 1 | Функции системы 2 | Компонент системы 1 | Компоненты системы 2 | Примечания |
| --- | --- | --- | --- | --- | --- | --- |
| dcActivate | Discrete | DC передаёт данные MBS | MBC принимает данные EC | DC | MBS | f(f, dce) |
| dcActivate | Discrete | DC передаёт данные EM | EM принимает данные EC | DC | EM | f(f, dce) |
| dcActivate | Discrete | C передаёт данные V | V принимает данные EC | DC | V | f(f, dce) |
| fuel | Analog | DE передаёт данные DC | DC принимает данные DE | DE | DC | f |
| dcEnable | Discrete | CP передаёт данные DC | DC принимает данные CP | CP | DC | dce |
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Рисунок 2 – Схема подключения DC

### 3 Электромоторы (EM): Электромоторы (EM) (Functional)
3 Электромоторы (EM)
В таблице 3 указаны характеристики работы электромоторов при разных режимах работы. Ускорение равно 1 километр в час в секунду.
Таблица 3 – Характеристики работы электромоторов
| Режим работы | Скорость (километр в час) | Потребление заряда батарей (условная единица в минуту) |
| --- | --- | --- |
| Самый полный вперёд | 19 | 7 |
| Полный вперёд | 16 | 6 |
| Средний вперёд | 13 | 5 |
| Малый вперёд | 10 | 3 |
| Самый малый вперёд | 6 | 1 |
| Обе машины стоп | 0 | 0 |
| Зарядка батарей | 0 | 0 |
| Самый малый назад | -9 | 3 |
| Малый назад | -12 | 4 |
| Средний назад | -14 | 5 |
| Самый полный назад | -16 | 6 |
На рисунке 3 указана схема подключения DC, в таблице 4 – характеристики интерфейсов
Таблица 4 – Характеристика интерфейсов DC
| Имя интерфейса | Тип интерфейса | Функции системы 1 | Функции системы 2 | Компонент системы 1 | Компоненты системы 2 | Примеча-ния |
| --- | --- | --- | --- | --- | --- | --- |
| emWorkMode | Analog | EM передаёт данные G | G принимает данные EM | EM | G | f(ece, dewm, pa, emom, eme) |
| batteryCharge | Analog | EM передаёт данные EC | EC принимает данные EM | EM | EC | f(ece, dewm, pa, emom, eme) |
| batteryCharge | Analog | EM передаёт данные DE | E принимает данные EM | EM | DE | f(ece, dewm, pa, emom, eme) |
| batteryCharge | Analog | EM передаёт данные P | P принимает данные EM | EM | P | f(ece, dewm, pa, emom, eme) |
| ecActivate | Discrete | EC передаёт данные EM | EM принимает данные EC | EC | EM | eca |
| deWorkMode | Analog | DE передаёт данные EM | EM принимает данные DE | DE | EM | dewm |
| pActivate | Analog | P передаёт данные EM | EM принимает данные P | P | EM | pa |
| operatingMode | Analog | MT передаёт данные EM | EM принимает данные MT | MT | EM | emom |
| emEnable | Discrete | MT передаёт данные EM | EM принимает данные MT | MT | EM | eme |
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Рисунок 3 – Схема подключения DC

#### 3.1 Заряд батарей (BC) (Functional)
3.1 Заряд батарей (BC)
100% заряда батарей составляют 3000 условных единиц.
