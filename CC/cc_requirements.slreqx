# cc_requirements

## cc_requirements: References to cc_requirements.docx (Container)
Read-only references to Microsoft Word document.
- srcFileChecksum: 781AF0E133895A49196050AE80B2C763

### 1 ЦЕНТРАЛЬНЫЙ ОТСЕК (CC) (Functional)
1 ÖÅÍÒÐÀËÜÍÛÉ ÎÒÑÅÊ (CC)

#### 1 Помпа (P) (Functional)
1 Ïîìïà (P)
Ïîìïà îòêà÷èâàåò âîäó èç âñåõ îòñåêîâ. Íàèáîëüøàÿ ýôôåêòèâíîñòü äîñòèãàåòñÿ ïðè îòêà÷êå âîäû èç öåíòðàëüíîãî îòñåêà.
Ìîæåò óìåíüøàòü óðîâåíü âîäû â îòñåêàõ íà 4 ìåòðà êóáè÷åñêèõ â ìèíóòó çà 12 óñëîâíûõ åäèíèö çàðÿäà áàòàðåè â ìèíóòó.
Íà ðèñóíêå 9.1 óêàçàíà ñõåìà ïîäêëþ÷åíèÿ P, â òàáëèöå 9.1 – õàðàêòåðèñòèêè èíòåðôåéñîâ
Òàáëèöà 9.1 – Õàðàêòåðèñòèêà èíòåðôåéñîâ P
| Èìÿ èíòåðôåéñà | Òèï èíòåðôåéñà | Ôóíêöèè ñèñòåìû 1 | Ôóíêöèè ñèñòåìû 2 | Êîìïîíåíò ñèñòåìû 1 | Êîìïîíåíòû ñèñòåìû 2 | Ïðèìå÷àíèÿ |
| --- | --- | --- | --- | --- | --- | --- |
| pActivate | Discrete | P ïåðåäà¸ò äàííûå EM | EM ïðèíèìàåò äàííûå P | P | EM | f(bc, pe) |
| batteryCharge | Analog | EM ïåðåäà¸ò äàííûå P | P ïðèíèìàåò äàííûå EM | EM | P | bc |
| pEnable | Discrete | CP ïåðåäà¸ò äàííûå P | P ïðèíèìàåò äàííûå CP | CP | P | pe |
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Ðèñóíîê 9.1 – Ñõåìà ïîäêëþ÷åíèÿ P

#### 2 Эхолот (ES) (Functional)
2 Ýõîëîò (ES)
Ýõîëîò èçìåðÿåò òåêóùóþ ãëóáèíó. Óëüòðàçâóêîâîé ñèãíàë ýôôåêòèâåí äî 150 ìåòðîâ. Çâóêîâîé ñèãíàë ýôôåêòèâåí íà ëþáîé ãëóáèíå.
2.1 Ãëóáèíîìåð (DG)
Ýõîëîò â äàííîé ðåâèçèè âûïîëíÿåò ôóíêöèè ãëóáèíîìåðà.
Íà ðèñóíêå 9.2 óêàçàíà ñõåìà ïîäêëþ÷åíèÿ ES, â òàáëèöå 9.2 – õàðàêòåðèñòèêè èíòåðôåéñîâ
Òàáëèöà 9.2 – Õàðàêòåðèñòèêà èíòåðôåéñîâ ES
| Èìÿ èíòåðôåéñà | Òèï èíòåðôåéñà | Ôóíêöèè ñèñòåìû 1 | Ôóíêöèè ñèñòåìû 2 | Êîìïîíåíò ñèñòåìû 1 | Êîìïîíåíòû ñèñòåìû 2 | Ïðèìå÷àíèÿ |
| --- | --- | --- | --- | --- | --- | --- |
| depth | Analog | ES ïåðåäà¸ò äàííûå DE | DE ïðèíèìàåò äàííûå ES | ES | DE | f(sp, fs, rs, fl) |
| depth | Analog | ES ïåðåäà¸ò äàííûå V | V ïðèíèìàåò äàííûå ES | ES | V | f(sp, fs, rs, fl) |
| depth | Analog | ES ïåðåäà¸ò äàííûå MBS | MBS ïðèíèìàåò äàííûå ES | ES | MBS | f(sp, fs, rs, fl) |
| depth | Analog | ES ïåðåäà¸ò äàííûå S | S ïðèíèìàåò äàííûå ES | ES | S | f(sp, fs, rs, fl) |
| speed | Analog | G ïåðåäà¸ò äàííûå ES | ES ïðèíèìàåò äàííûå G | G | ES | sp |
| frontSlant | Analog | DR ïåðåäà¸ò äàííûå ES | ES ïðèíèìàåò äàííûå DR | DR | ES | fs |
| rearSlant | Analog | DR ïåðåäà¸ò äàííûå ES | ES ïðèíèìàåò äàííûå DR | DR | ES | rs |
| floodingLevel | Analog | MBS ïåðåäà¸ò äàííûå ES | ES ïðèíèìàåò äàííûå MBS | MBS | ES | fl |
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Ðèñóíîê 9.2 – Ñõåìà ïîäêëþ÷åíèÿ ES

#### 3 Гирокомпас (G) (Functional)
3 Ãèðîêîìïàñ (G)
Ðàáîòàþùèé ãèðîêîìïàñ ïîâûøàåò òî÷íîñòü íàâèãàöèè. Ãèðîêîìïàñ – ýòî íàâèãàöèîííûé ïðèáîð, êîòîðûé èñïîëüçóåò óãëîâîé ìîìåíò äëÿ îïðåäåëåíèÿ íàïðàâëåíèÿ îòíîñèòåëüíî Ñåâåðà. Îí â ÷åòûðå ðàçà òî÷íåå ìàãíèòíîãî êîìïàñà è íå çàâèñèò îò ìàãíèòíûõ ïîëåé, îñòàâàÿñü óñòîé÷èâûì ïðè ðàçëè÷íûõ ìàí¸âðàõ è óñëîâèÿõ.
Ãèðîêîìïàñ ïîòðåáëÿåò 1 óñëîâíóþ åäèíèöó çàðÿäà áàòàðåè â ìèíóòó.
3.1 Êîîðäèíàòû (CS)
Â äàííîé ðåâèçèè õðàíèò êîîðäèíàòû ïîäëîäêè â äåñÿòè÷íîì ôîðìàòå.
Íà ðèñóíêå 9.3 óêàçàíà ñõåìà ïîäêëþ÷åíèÿ G, â òàáëèöå 9.3 – õàðàêòåðèñòèêè èíòåðôåéñîâ
Òàáëèöà 9.3 – Õàðàêòåðèñòèêà èíòåðôåéñîâ G
| Èìÿ èíòåðôåéñà | Òèï èíòåðôåéñà | Ôóíêöèè ñèñòåìû 1 | Ôóíêöèè ñèñòåìû 2 | Êîìïîíåíò ñèñòåìû 1 | Êîìïîíåíòû ñèñòåìû 2 | Ïðèìå÷àíèÿ |
| --- | --- | --- | --- | --- | --- | --- |
| speed | Analog | G ïåðåäà¸ò äàííûå DE | DE ïðèíèìàåò äàííûå G | G | ES | f(dewm, emwm) |
| deWorkMode | Analog | DE ïåðåäà¸ò äàííûå G | G ïðèíèìàåò äàííûå DE | DE | G | dewm |
| emWorkMode | Analog | EM ïåðåäà¸ò äàííûå G | G ïðèíèìàåò äàííûå EM | EM | G | emwm |
| axio | Analog | A ïåðåäà¸ò äàííûå G | G ïðèíèìàåò äàííûå A | A | G |  |
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Ðèñóíîê 9.3 – Ñõåìà ïîäêëþ÷åíèÿ G

#### 4 Вентили балластных цистерн (BTS) (Functional)
4 Âåíòèëè áàëëàñòíûõ öèñòåðí (BTS)
Âåíòèëè áàëëàñòíûõ öèñòåðí íà çàïîëíåíèå ïðèíèìàþò çíà÷åíèÿ ñ 0% äî 100% ïðèìåðíî çà 5 ñåêóíä.
Âåíòèëè áàëëàñòíûõ öèñòåðí íà çàïîëíåíèå ïðèíèìàþò çíà÷åíèÿ ñî 100% äî 0% ïðèìåðíî çà 5 ñåêóíä.
Âåíòèëè áàëëàñòíûõ öèñòåðí íà ïðîäóâ ïðèíèìàþò çíà÷åíèÿ ñ 0% äî 100% ïðèìåðíî çà 5 ñåêóíä.
Âåíòèëè áàëëàñòíûõ öèñòåðí íà ïðîäóâ ïðèíèìàþò çíà÷åíèÿ ñî 100% äî 0% ïðèìåðíî çà 5 ñåêóíä.
Íà ðèñóíêå 9.4 óêàçàíà ñõåìà ïîäêëþ÷åíèÿ BTS, â òàáëèöå 9.4 – õàðàêòåðèñòèêè èíòåðôåéñîâ
Òàáëèöà 9.4 – Õàðàêòåðèñòèêà èíòåðôåéñîâ BTS
| Èìÿ èíòåðôåéñà | Òèï èíòåðôåéñà | Ôóíêöèè ñèñòåìû 1 | Ôóíêöèè ñèñòåìû 2 | Êîìïîíåíò ñèñòåìû 1 | Êîìïîíåíòû ñèñòåìû 2 | Ïðèìå÷àíèÿ |
| --- | --- | --- | --- | --- | --- | --- |
| fillingValve1 | Analog | MBS ïåðåäà¸ò äàííûå BTS | BTS ïðèíèìàåò äàííûå MBS | MBS | BTS |  |
| fillingValve2 | Analog | MBS ïåðåäà¸ò äàííûå BTS | BTS ïðèíèìàåò äàííûå MBS | MBS | BTS |  |
| fillingValve3 | Analog | MBS ïåðåäà¸ò äàííûå BTS | BTS ïðèíèìàåò äàííûå MBS | MBS | BTS |  |
| fillingValve4 | Analog | MBS ïåðåäà¸ò äàííûå BTS | BTS ïðèíèìàåò äàííûå MBS | MBS | BTS |  |
| fillingValve5 | Analog | MBS ïåðåäà¸ò äàííûå BTS | BTS ïðèíèìàåò äàííûå MBS | MBS | BTS |  |
| purgingValves | Analog | MBS ïåðåäà¸ò äàííûå BTS | BTS ïðèíèìàåò äàííûå MBS | MBS | BTS |  |
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Ðèñóíîê 9.4 – Ñõåìà ïîäêëþ÷åíèÿ BTS

#### 5 Рули глубины (DR) (Functional)
5 Ðóëè ãëóáèíû (DR)
Ïåðåäíèå ðóëè ïðèíèìàþò çíà÷åíèÿ îò -35 äî 35 ãðàäóñîâ âåðòèêàëüíîãî îòêëîíåíèÿ.
Çàäíèå ðóëè ïðèíèìàþò çíà÷åíèÿ îò -40 äî 40 ãðàäóñîâ âåðòèêàëüíîãî îòêëîíåíèÿ.
Ñêîðîñòü èçìåíåíèÿ ïîëîæåíèÿ ðóëÿ ðàâíî 1 ãðàäóñ â ñåêóíäó.
Íà ðèñóíêå 9.5 óêàçàíà ñõåìà ïîäêëþ÷åíèÿ DR, â òàáëèöå 9.5 – õàðàêòåðèñòèêè èíòåðôåéñîâ
Òàáëèöà 9.5 – Õàðàêòåðèñòèêà èíòåðôåéñîâ BTS
| Èìÿ èíòåðôåéñà | Òèï èíòåðôåéñà | Ôóíêöèè ñèñòåìû 1 | Ôóíêöèè ñèñòåìû 2 | Êîìïîíåíò ñèñòåìû 1 | Êîìïîíåíòû ñèñòåìû 2 | Ïðèìå÷àíèÿ |
| --- | --- | --- | --- | --- | --- | --- |
| frontSlant | Analog | DR ïåðåäà¸ò äàííûå ES | ES ïðèíèìàåò äàííûå DR | DR | ES |  |
| rearSlant | Analog | DR ïåðåäà¸ò äàííûå ES | ES ïðèíèìàåò äàííûå DR | DR | ES |  |
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Ðèñóíîê 9.5 – Ñõåìà ïîäêëþ÷åíèÿ BTS

#### 6 Машинный телеграф (MT) (Functional)
6 Ìàøèííûé òåëåãðàô (MT)
Ìàøèííûé òåëåãðàô èìååò 11 ïîëîæåíèé.
1) Ñàìûé ïîëíûé âïåð¸ä
2) Ïîëíûé âïåð¸ä
3) Ñðåäíèé âïåð¸ä
4) Ìàëûé âïåð¸ä
5) Ñàìûé ìàëûé âïåð¸ä
6) Îáå ìàøèíû ñòîï
7) Çàðÿäêà áàòàðåé
8) Ñàìûé ìàëûé íàçàä
9) Ìàëûé íàçàä
10) Ñðåäíèé íàçàä
11) Ñàìûé ïîëíûé íàçàä
È ïåðåêëþ÷àòåëü ìàðøåâîé óñòàíîâêè.
Íà ðèñóíêå 9.6 óêàçàíà ñõåìà ïîäêëþ÷åíèÿ MT, â òàáëèöå 9.6 – õàðàêòåðèñòèêè èíòåðôåéñîâ
Òàáëèöà 9.6 – Õàðàêòåðèñòèêà èíòåðôåéñîâ MT
| Èìÿ èíòåðôåéñà | Òèï èíòåðôåéñà | Ôóíêöèè ñèñòåìû 1 | Ôóíêöèè ñèñòåìû 2 | Êîìïîíåíò ñèñòåìû 1 | Êîìïîíåíòû ñèñòåìû 2 | Ïðèìå÷àíèÿ |
| --- | --- | --- | --- | --- | --- | --- |
| operatingMode | Analog | MT ïåðåäà¸ò äàííûå DE | DE ïðèíèìàåò äàííûå MT | MT | DE |  |
| operatingMode | Analog | MT ïåðåäà¸ò äàííûå DE | DE ïðèíèìàåò äàííûå MT | MT | EM |  |
| deEnable | Discrete | MT ïåðåäà¸ò äàííûå DE | DE ïðèíèìàåò äàííûå MT | MT | DE |  |
| emEnable | Discrete | MT ïåðåäà¸ò äàííûå DE | DE ïðèíèìàåò äàííûå MT | MT | EM |  |
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Ðèñóíîê 9.6 – Ñõåìà ïîäêëþ÷åíèÿ MT

#### 7 Аксиометр (A) (Functional)
7 Àêñèîìåòð (A)
Àêñèîìåòð ïðèíèìàåò çíà÷åíèÿ îò -35 äî 35 ãîðèçîíòàëüíîãî îòêëîíåíèÿ.
Ñêîðîñòü èçìåíåíèÿ ïîëîæåíèÿ ðóëÿ ðàâíî 1 ãðàäóñ â ñåêóíäó.
Íà ðèñóíêå 9.7 óêàçàíà ñõåìà ïîäêëþ÷åíèÿ A, â òàáëèöå 9.7 – õàðàêòåðèñòèêè èíòåðôåéñîâ
Òàáëèöà 9.7 – Õàðàêòåðèñòèêà èíòåðôåéñîâ A
| Èìÿ èíòåðôåéñà | Òèï èíòåðôåéñà | Ôóíêöèè ñèñòåìû 1 | Ôóíêöèè ñèñòåìû 2 | Êîìïîíåíò ñèñòåìû 1 | Êîìïîíåíòû ñèñòåìû 2 | Ïðèìå÷àíèÿ |
| --- | --- | --- | --- | --- | --- | --- |
| axio | Analog | A ïåðåäà¸ò äàííûå G | G ïðèíèìàåò äàííûå A | A | G |  |
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Ðèñóíîê 9.6 – Ñõåìà ïîäêëþ÷åíèÿ A
