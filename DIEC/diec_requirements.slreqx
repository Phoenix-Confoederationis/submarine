# diec_requirements

## diec_requirements: References to diec_requirements.docx (Container)
Read-only references to Microsoft Word document.

### ДИЗЕЛЬНЫЙ ОТСЕК (DIEC) (Functional)

#### 1 Дизеля (DE) (Functional)
1 Дизеля (DE)
В таблице 1 указаны характеристики работы дизеля в разных режимах работы. Дизеля не могут работать на любой глубине. Ускорение равно 2 километра в час в секунду.
Таблица 1 – Характеристики работы дизеля
| Режим работы | Скорость (километр в час) | Потребление топлива (литр в минуту) | Восполнение заряда батарей (условная единица в минуту) |
| --- | --- | --- | --- |
| Самый полный вперёд | 32 | 7,7 \| 7,7 | 0 |
| Полный вперёд | 28 | 8,6 \| 7,6 | 20,2 |
| Средний вперёд | 24 | 7,6 \| 4,4 | 64,7 |
| Малый вперёд | 18 | 6 \| 3,3 | 62,7 |
| Самый малый вперёд | 6 | 8,2 \| 2,6 | 128,9 |
| Обе машины стоп | 0 | 0 \| 0 | 0 |
| Зарядка батарей | 0 | 2 \| 0 | 50 |
| Самый малый назад | -10 | 4,6 \| 2 | 65,2 |
| Малый назад | -14 | 4,2 \| 2 | 49,9 |
| Средний назад | -18 | 4,3 \| 2,8 | 34 |
| Самый полный назад | -20 | 4,6 \| 4,6 | 0 |

##### 1.1 Топливо (F) (Functional)
1.1 Топливо (F)
100% топлива составляют 50000 литров.
На рисунке 1 указана схема подключения DE, в таблице 2 – характеристики интерфейсов
Таблица 2 – Характеристика интерфейсов DE
| Имя интерфейса | Тип интерфейса | Функции системы 1 | Функции системы 2 | Компонент системы 1 | Компоненты системы 2 | Примечания |
| --- | --- | --- | --- | --- | --- | --- |
| fuel | Analog | DE передаёт данные DC | DC принимает данные DE | DE | DC | f(dca, bc, sa, d, deom, dee) |
| deWorkMode | Analog | DE передаёт данные EM | EM принимает данные DE | DE | EM | f(dca, bc, sa, d, deom, dee) |
| deWorkMode | Analog | DE передаёт данные G | G принимает данные DE | DE | G | f(dca, bc, sa, d, deom, dee) |
| dcActivate | Discrete | DC передаёт данные DE | DE принимает данные DC | DC | DE | dca |
| batteryCharge | Analog | EM передаёт данные DE | DE принимает данные EM | EM | DE | bc |
| sActivate | Discrete | S передаёт данные DE | DE принимает данные S | S | DE | sa |
| depth | Analog | ES передаёт данные DE | DE принимает данные ES | ES | DE | d |
| operatingMode | Analog | MT передаёт данные DE | DE принимает данные MT | MT | DE | deom |
| deEnable | Discrete | MT передаёт данные DE | DE принимает данные MT | MT | DE | dee |
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Рисунок 1 – Схема подключения DE

#### 2 Шноркель (S) (Functional)
2 Шноркель (S)
Система труб, которая может быть выдвинута над поверхностью воды для забора свежего воздуха и обеспечения работы дизелей в подводном положении. Работает только до перископной глубины (до 8 метров).
Восполняет 400 условных единиц качества воздуха в минуту.
На рисунке 2 указана схема подключения S, в таблице 3 – характеристики интерфейсов
Таблица 3 – Характеристика интерфейсов S
| Имя интерфейса | Тип интерфейса | Функции системы 1 | Функции системы 2 | Компонент системы 1 | Компоненты системы 2 | Примечания |
| --- | --- | --- | --- | --- | --- | --- |
| sActivate | Discrete | S передаёт данные DE | DE принимает данные DE | S | DE | f(d,se) |
| sActivate | Discrete | S передаёт данные V | V принимает данные DE | S | V | f(d,se) |
| depth | Analog | ES передаёт данные S | S принимает данные ES | ES | S | d |
| sEnable | Discrete | CP передаёт данные S | S принимает данные CP | CP | S | se |
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Рисунок 2 – Схема подключения S

#### 3 Вентиляция (V) (Functional)
3 Вентиляция (V)
Вентиляция повышает качество воздуха для дыхания в течение ограниченного времени.
Во время работы вентиляция восполняет 5 условных единиц качества воздуха в минуту.

##### 3.1 Качество воздуха (AQ) (Functional)
3.1 Качество воздуха (AQ)
100% качества воздуха – 3000 условных единиц.
Экипаж потребляет 6 условных единиц качества воздуха в минуту.
Когда подводная лодка находиться на поверхности свежий воздух восполняет 6000 условных единиц качества воздуха в минуту.
На рисунке 3 указана схема подключения V, в таблице 4 – характеристики интерфейсов
Таблица 4 – Характеристика интерфейсов V
| Имя интерфейса | Тип интерфейса | Функции системы 1 | Функции системы 2 | Компонент системы 1 | Компоненты системы 2 | Примечания |
| --- | --- | --- | --- | --- | --- | --- |
| ecActivate | Discrete | EC передаёт данные V | V принимает данные EC | EC | V |  |
| dcActivate | Discrete | DC передаёт данные V | V принимает данные DC | DC | V |  |
| sActivate | Discrete | EM передаёт данные V | V принимает данные S | S | V |  |
| depth | Analog | ES передаёт данные V | V принимает данные ES | ES | V |  |
| vEnable | Discrete | CP передаёт данные V | V принимает данные CP | CP | V |  |
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Рисунок 3 – Схема подключения V
