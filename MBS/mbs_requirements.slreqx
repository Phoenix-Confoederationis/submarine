# mbs_requirements

## mbs_requirements: References to mbs_requirements.docx (Container)
Read-only references to Microsoft Word document.

### 4 ГЛАВНАЯ БАЛЛАСТНАЯ ЦИСТЕРНА (MBS) (Functional)
4 ГЛАВНАЯ БАЛЛАСТНАЯ ЦИСТЕРНА (MBS)
Существует 5 независимых друг от друга балластных цистерн.
Каждая балластная цистерна может изменить уровень затопления с 0 до 100% примерно за 12,5 секунд при 1 атмосфере.
Главная балластная цистерна может изменить уровень затопления с 100% до 0% примерно за 30 секунд, потратив 70 атмосфер сжатого воздуха при 1 атмосфере.
При 0% заполнении балластных цистерн подводная лодка имеет положительную плавучесть (1,66 метров в секунду к поверхности).
При 100% заполнении балластных цистерн подводная лодка имеет нейтральную плавучесть.
В данной ревизии хранит запас сжатого воздуха.
На рисунке 4.1 указана схема подключения MBS, в таблице 4.1 – характеристики интерфейсов
Таблица 4.1 – Характеристика интерфейсов MBS
| Имя интерфейса | Тип интерфейса | Функции системы 1 | Функции системы 2 | Компонент системы 1 | Компоненты системы 2 | Примечания |
| --- | --- | --- | --- | --- | --- | --- |
| floodingLevel | Analog | MBS предаёт данные ES | ES принимает данные MBS | MBS | ES | f(fv1, fv2, fv3, fv4, fv5, pv, d, c) |
| fillingValve1 | Analog | BTS передаёт данные MBS | MBS принимает данные BTS | BTS | MBS | fv1 |
| fillingValve2 | Analog | BTS передаёт данные MBS | MBS принимает данные BTS | BTS | MBS | fv2 |
| fillingValve3 | Analog | BTS передаёт данные MBS | MBS принимает данные BTS | BTS | MBS | fv3 |
| fillingValve4 | Analog | BTS передаёт данные MBS | MBS принимает данные BTS | BTS | MBS | fv4 |
| fillingValve5 | Analog | BTS передаёт данные MBS | MBS принимает данные BTS | BTS | MBS | fv5 |
| purgingValves | Analog | BTS передаёт данные MBS | MBS принимает данные BTS | BTS | MBS | pv |
| depth | Analog | ES передаёт данные MBS | MBS принимает данные ES | ES | MBS | d |
| ecActivate | Discrete | EC передаёт данные MBS | EC принимает данные BTS | EC | MBS | eca |
| dcActivate | Discrete | DC передаёт данные MBS | MBS принимает данные DC | DC | MBS | dca |
| compressedAir | Analog | Внутренний сигнал |  | MBS |  | f(pv, ec, dca)=c |
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Рисунок 4.1 – Схема подключения MBS
